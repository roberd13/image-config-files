DATASTAX-OPSCALERT-MIB DEFINITIONS ::= BEGIN

IMPORTS
    NOTIFICATION-GROUP, OBJECT-GROUP
        FROM SNMPv2-CONF
    Integer32, MODULE-IDENTITY, NOTIFICATION-TYPE, OBJECT-TYPE,
    enterprises
        FROM SNMPv2-SMI;

dataStaxOpscAlertTrap MODULE-IDENTITY
    LAST-UPDATED "201507060000Z"
    ORGANIZATION
        "www.datastax.com"
    CONTACT-INFO
        "jack.kingsman@datastax.com"
    DESCRIPTION
        "Notification information for OPSC alerts"
    REVISION    "201507060000Z"
    DESCRIPTION
        "First Draft"
    ::= { opscAlerts 1 }


datastax OBJECT IDENTIFIER
    ::= { enterprises 46272 }

opsc OBJECT IDENTIFIER
    ::= { datastax 1 }

opscAlerts OBJECT IDENTIFIER
    ::= { opsc 0 }

opscAlertTable OBJECT-TYPE
    SYNTAX      SEQUENCE OF OpscAlertEntry
    MAX-ACCESS  not-accessible
    STATUS      current
    DESCRIPTION
        "Information on alerts generated by OpsCenter. This table is not queryable; it exists only to document the variables included in the opscAlert trap.  Each trap contains a single instance of each variable in the table."
    ::= { opscAlerts 2 }

opscAlertEntry OBJECT-TYPE
    SYNTAX      OpscAlertEntry
    MAX-ACCESS  not-accessible
    STATUS      current
    DESCRIPTION
        "Information about a particular OpsCenter alert."
    INDEX       { opscAlertIndex }
    ::= { opscAlertTable 1 }

OpscAlertEntry ::= SEQUENCE {
    opscAlertIndex      Integer32,
    opscAlertLevel      Integer32,
    opscAlertLevelStr   OCTET STRING,
    opscAlertMessage    OCTET STRING,
    opscAlertAction     Integer32,
    opscAlertCluster    OCTET STRING,
    opscAlertEventSrc   OCTET STRING,
    opscAlertSrcNode    OCTET STRING,
    opscAlertTargNode   OCTET STRING,
    opscAlertEpochTime  OCTET STRING,
    opscAlertStrTime    OCTET STRING,
    opscAlertAPISrcIP   OCTET STRING,
    opscAlertUser       OCTET STRING
}

opscAlertIndex OBJECT-TYPE
    SYNTAX      Integer32 (1..2147483647)
    MAX-ACCESS  not-accessible
    STATUS      current
    DESCRIPTION
        "Index of a particular alert, unique only at the moment an alert is generated."
    ::= { opscAlertEntry 1 }

opscAlertLevel OBJECT-TYPE
    SYNTAX      Integer32
    MAX-ACCESS  read-only
    STATUS      current
    DESCRIPTION
        "The ID of the severity level for this alert."
    ::= { opscAlertEntry 2 }

opscAlertLevelStr OBJECT-TYPE
    SYNTAX      OCTET STRING
    MAX-ACCESS  read-only
    STATUS      current
    DESCRIPTION
        "The english string of the severity level for this alert."
    ::= { opscAlertEntry 3 }

opscAlertMessage OBJECT-TYPE
    SYNTAX      OCTET STRING
    MAX-ACCESS  read-only
    STATUS      current
    DESCRIPTION
        "The description of the event that triggered the alert."
    ::= { opscAlertEntry 4 }

opscAlertAction OBJECT-TYPE
    SYNTAX      Integer32
    MAX-ACCESS  read-only
    STATUS      current
    DESCRIPTION
        "The numerical type of event that triggered the alert."
    ::= { opscAlertEntry 5 }

opscAlertCluster OBJECT-TYPE
    SYNTAX      OCTET STRING
    MAX-ACCESS  read-only
    STATUS      current
    DESCRIPTION
        "The name of the cluster on which the event was triggered."
    ::= { opscAlertEntry 6 }

opscAlertEventSrc OBJECT-TYPE
    SYNTAX      OCTET STRING
    MAX-ACCESS  read-only
    STATUS      current
    DESCRIPTION
        "The name of the node on which the event was triggered."
    ::= { opscAlertEntry 7 }

opscAlertSrcNode OBJECT-TYPE
    SYNTAX      OCTET STRING
    MAX-ACCESS  read-only
    STATUS      current
    DESCRIPTION
        "The IP of the node on which the event was triggered."
    ::= { opscAlertEntry 8 }

opscAlertTargNode OBJECT-TYPE
    SYNTAX      OCTET STRING
    MAX-ACCESS  read-only
    STATUS      current
    DESCRIPTION
        "The destination of a STREAMING action."
    ::= { opscAlertEntry 9 }

opscAlertEpochTime OBJECT-TYPE
    SYNTAX      OCTET STRING
    MAX-ACCESS  read-only
    STATUS      current
    DESCRIPTION
        "The time of event occurrence as a Unix Epoch timestamp."
    ::= { opscAlertEntry 10 }

opscAlertStrTime OBJECT-TYPE
    SYNTAX      OCTET STRING
    MAX-ACCESS  read-only
    STATUS      current
    DESCRIPTION
        "The date and time that the event occurred."
    ::= { opscAlertEntry 11 }

opscAlertAPISrcIP OBJECT-TYPE
    SYNTAX      OCTET STRING
    MAX-ACCESS  read-only
    STATUS      current
    DESCRIPTION
        "The IP that originally sent the request."
    ::= { opscAlertEntry 12 }

opscAlertUser OBJECT-TYPE
    SYNTAX      OCTET STRING
    MAX-ACCESS  read-only
    STATUS      current
    DESCRIPTION
        "The OpsCenter user that caused the event."
    ::= { opscAlertEntry 13 }

opscAlert NOTIFICATION-TYPE
    OBJECTS     { opscAlertLevel, opscAlertLevelStr, opscAlertMessage,
                  opscAlertAction, opscAlertCluster, opscAlertEventSrc,
                  opscAlertSrcNode, opscAlertTargNode,
                  opscAlertEpochTime, opscAlertStrTime,
                  opscAlertAPISrcIP, opscAlertUser }
    STATUS      current
    DESCRIPTION
        "OpsCenter Event Trap"
    ::= { opscAlerts 3 }

opscAlertElements OBJECT-GROUP
    OBJECTS     { opscAlertLevel, opscAlertLevelStr, opscAlertMessage,
                  opscAlertAction, opscAlertCluster, opscAlertEventSrc,
                  opscAlertSrcNode, opscAlertTargNode,
                  opscAlertEpochTime, opscAlertStrTime,
                  opscAlertAPISrcIP, opscAlertUser }
    STATUS      current
    DESCRIPTION
        "Elements within the OpsCenter Event Trap"
    ::= { opscAlerts 4 }

opscAlertGroup NOTIFICATION-GROUP
    NOTIFICATIONS { opscAlert }
    STATUS      current
    DESCRIPTION
        "The notifications sent by OPSC."
    ::= { opscAlerts 5 }

END
